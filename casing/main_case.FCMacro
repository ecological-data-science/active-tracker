from FreeCAD import Base
import FreeCAD as App
import BOPTools.JoinFeatures
import Part
import Part,PartGui
import Mesh
import sys,os

sys.path.append('/Users/colin.torney/workspace/active-tracker/casing')

from base_case import build_base_case
from top_case import build_top_case

import importlib

importlib.reload(sys.modules['base_case'])
importlib.reload(sys.modules['top_case'])


doc = App.activeDocument()

def clean():
    objs = doc.Objects
    for obj in objs:
        name = obj.Name
        doc.removeObject(name)

def main():
    doc = App.activeDocument()
    clean()
    basecase = build_base_case(doc)
    topcase = build_top_case(doc)

if __name__ == "__main__":
    main()
